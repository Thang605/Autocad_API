(defun c:cogoelev (/ ele n ss)
  (if (and (setq ele (getreal "\Enter elevation: "))
      (setq ss (ssget ":L" '((0 . "AECC_COGO_POINT"))))
      )
    (repeat (setq n (sslength ss))
      (vla-put-elevation (vlax-ename->vla-object (ssname ss (setq n (1- n)))) ele)
    )
  )
  (princ)
)
