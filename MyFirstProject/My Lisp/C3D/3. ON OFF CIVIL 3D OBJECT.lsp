;; Bat tat corridor Section
   (Defun c:OffCorridorSection ( )  
 	 (command "-layer" "OFF" "C-ROAD-CORR-LINK" "")
   (Princ)
)  
   (Defun c:OnCorridorSection ( )  
 	 (command "-layer" "On" "C-ROAD-CORR-LINK" "")
   (Princ)
)  
;; Bat tat Sampleline
   (Defun c:OnSampleLine ( )  
 	 (command "-layer" "On" "C-ROAD-SAMP" "")
   (Princ)
)  
   (Defun c:OffSampleLine ( )  
 	 (command "-layer" "OFF" "C-ROAD-SAMP" "")
   (Princ)
)  
   (Defun c:OffAlignment ( )  
 	 (command "-layer" "OFF" "C-ROAD-CNTR-off" "")
   (Princ)
)  
   (Defun c:OnAlignment ( )  
 	 (command "-layer" "ON" "C-ROAD-CNTR-off" "")
   (Princ)
)  
   (Defun c:Off ( )  
 	 (command "-layer" "OFF" "Defpoints" "")
   (Princ)
)  
   (Defun c:On ( )  
 	 (command "-layer" "ON" "Defpoints" "")
   (Princ)
)
   (Defun c:OffParcel ( )  
 	 (command "-layer" "OFF" "C-PROP-BNDY" "")
   (Princ)
)  
   (Defun c:OnParcel ( )  
 	 (command "-layer" "ON" "C-PROP-BNDY" "")
   (Princ)
)  
   (Defun c:OnHatchDaoDap ( )  
 	 (command "-layer" "ON" "$$$HATCH DAO DAP" "")
   (Princ)
)  
  (Defun c:OffHatchDaoDap ( )  
 	 (command "-layer" "OFF" "$$$HATCH DAO DAP" "")
   (Princ)
)  
  (Defun c:UpDateStyleOff ( )  
 	 (command "-AECCREFTEMPLATEAUTOUPDATE" 0)
   (Princ)
)
  (Defun c:UpDateStlyleOn ( )  
 	 (command "-AECCREFTEMPLATEAUTOUPDATE" 1)
   (Princ)
)
