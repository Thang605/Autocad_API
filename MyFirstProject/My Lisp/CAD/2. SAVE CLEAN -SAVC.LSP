(
Defun c:SAVC ( )  
   	(command "-PURGE" "A" "*" "N")
   	(command "-PURGE" "R" "*" "N")
	(command "-PURGE" "O")
   	(command "-PURGE" "Z")
   	(command "-PURGE" "B" "*" "N")
   	(command "-PURGE" "DE" "*" "N")
   	(command "-PURGE" "D" "*" "N")
   	(command "-PURGE" "G" "*" "N")
   	(command "-PURGE" "LA" "*" "N")
   	(command "-PURGE" "LT" "*" "N")
   	(command "-PURGE" "MA" "*" "N")
   	(command "-PURGE" "MU" "*" "N")
   	(command "-PURGE" "P" "*" "N")
   	(command "-PURGE" "SH" "*" "N")
   	(command "-PURGE" "ST" "*" "N")
   	(command "AUDIT" "Y")
	(command "QSAVE")
	(Princ)
)
