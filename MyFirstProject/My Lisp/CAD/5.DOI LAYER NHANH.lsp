;; free lisp from cadviet.com
;;; this lisp was downloaded from http://www.cadviet.com/forum/topic/31222-lisp-chuyen-layer/
   (Defun c:0 ( )  
   (Prompt "\nChon doi tuong muon chuyen lop...")
  (Setq chuyen (Ssget))
  (command "chprop" chuyen "" "la" "0.TEXT"  "")
	(Princ)
)  
  
(Defun c:00 ( )  
   (Prompt "\nChon doi tuong muon chuyen lop...")
  (Setq chuyen (Ssget))
  (command "chprop" chuyen "" "la" "Defpoints"  "")
	(Princ)
)  
  
(Defun c:11 ( )  
   (Prompt "\nChon doi tuong muon chuyen lop...")
  (Setq chuyen (Ssget))
  (command "chprop" chuyen "" "la" "1.DIM"  "")
	(Princ)
)  
(Defun c:22 ( )  
   (Prompt "\nChon doi tuong muon chuyen lop...")
  (Setq chuyen (Ssget))
  (command "chprop" chuyen "" "la" "2.BAO BT"  "")
	(Princ)
)
    
(Defun c:33 ( )  
   (Prompt "\nChon doi tuong muon chuyen lop...")
  (Setq chuyen (Ssget))
  (command "chprop" chuyen "" "la" "3.BAO COT THEP"  "")
	(Princ)
)
    
(Defun c:44 ( )  
   (Prompt "\nChon doi tuong muon chuyen lop...")
  (Setq chuyen (Ssget))
  (command "chprop" chuyen "" "la" "4.THEP"  "")
	(Princ)
)
    
(Defun c:55 ( )  
   (Prompt "\nChon doi tuong muon chuyen lop...")
  (Setq chuyen (Ssget))
  (command "chprop" chuyen "" "la" "5.TRUC"  "")
	(Princ)
)
    
(Defun c:66 ( )  
   (Prompt "\nChon doi tuong muon chuyen lop...")
  (Setq chuyen (Ssget))
  (command "chprop" chuyen "" "la" "6.KHUAT"  "")
	(Princ)
)
    
(Defun c:77 ( )  
   (Prompt "\nChon doi tuong muon chuyen lop...")
  (Setq chuyen (Ssget))
  (command "chprop" chuyen "" "la" "7.HATCH"  "")
	(Princ)
)

(Defun c:88 ( )  
   (Prompt "\nChon doi tuong muon chuyen lop...")
  (Setq chuyen (Ssget))
  (command "chprop" chuyen "" "la" "8.RANH GIOI"  "")
	(Princ)
)
