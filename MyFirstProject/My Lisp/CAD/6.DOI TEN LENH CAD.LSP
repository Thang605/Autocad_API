(
Defun c:UT ( )
	(command "AT_TextLayout")
		
	(Princ)
)

(
Defun c:UD ( )
	(command "AT_DimLayout")
		
	(Princ)
)

(
Defun c:UB ( )
	(command "AT_BlockLayout")
		
	(Princ)
)

(
Defun c:UTL ( )
	(command "AT_UpdateLayout")
		
	(Princ)
)

(
Defun c:TTL ( )
	(command "OBJECTSCALE")
		
	(Princ)
)

(
Defun c:k ( )
	(command "dimlinear")
		
	(Princ)
)

(
Defun c:kj ( )
	(command "_dimaligned")
		
	(Princ)
)

(
Defun c:c ( )
	(command "COPY")
		
	(Princ)
)
	

(
Defun c:ci ( )
	(command "CIRCLE")
		
	(Princ)
)
